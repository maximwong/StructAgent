;;; RCFLOOR 1.5 REPORT SYNC FONTFIX - AutoCAD 2022 full Windows version. ASCII source.
;;; Additional commands: RFFONTFIX (RF-TEXT only), RFDIAG (read-only).
;;; Commands: RFLOAD, RFPLAN, RFBEAMS, RFDETAIL, RFENV, RFTABLE, RFALL.
;;; Model coordinates are WCS mm. Data are read, never eval/load executed.
(defun rf:fail (msg) (princ (strcat "\nRCFLOOR: " msg)) (exit))
(vl-load-com)
(defun rf:unicode-probe () (ascii (chr 20013)))
(defun rf:unicode-ok (/ result)
  (setq result (vl-catch-all-apply 'rf:unicode-probe '()))
  (and (not (vl-catch-all-error-p result)) (= result 20013)))
(defun rf:require-unicode ()
  (if (not (rf:unicode-ok))
    (rf:fail "Unicode engine is not active. Set LISPSYS=1, close ALL AutoCAD windows, restart and APPLOAD this file again.")))
(defun rf:linetype (key / name pattern data n)
  (setq name (strcat "RF-" key)
    pattern (cond ((= key "CENTER") '(250.0 -60.0 0.0 -60.0))
      ((= key "HIDDEN") '(100.0 -60.0)) (T '(65.0 -35.0))))
  (if (not (tblsearch "LTYPE" name))
    (progn
      (setq data (list '(0 . "LTYPE") '(100 . "AcDbSymbolTableRecord")
        '(100 . "AcDbLinetypeTableRecord") (cons 2 name) '(70 . 0) (cons 3 name)
        '(72 . 65) (cons 73 (length pattern)) (cons 40 (apply '+ (mapcar 'abs pattern)))))
      (foreach n pattern (setq data (append data (list (cons 49 n) '(74 . 0)))))
      (if (not (entmake data)) (rf:fail "Cannot create RF line type"))))
  name)
(defun rf:layer (key / name col lw codes en ed lt)
  (setq name (strcat "RF-" key))
  (if (> (getvar "LISPSYS") 0)
    (progn
      (setq codes (cdr (assoc key '(("CONC" 28151 20957 22303) ("REBAR" 38050 31563)
        ("STIRRUP" 31629 31563) ("DIM" 26631 27880) ("TEXT" 25991 23383)
        ("AXIS" 36724 32447) ("ENV" 20869 21147 21253 32476) ("CENTER" 28857 21010 36724 32447) ("HIDDEN" 36974 25377 36718 24275) ("ERECT" 26550 31435 31563)))))
      (if codes (setq name (strcat name "-" (apply 'strcat (mapcar 'chr codes)))))))
  (setq col (cond ((= key "REBAR") 1) ((= key "STIRRUP") 3) ((member key '("AXIS" "CENTER")) 8) (T 7)))
  (setq lw (cond ((= key "REBAR") 35) ((= key "CONC") 25) ((member key '("AXIS" "CENTER" "HIDDEN")) 13) ((= key "ERECT") 25) (T 18)))
  (if (not (tblsearch "LAYER" name))
    (entmake (list '(0 . "LAYER") '(100 . "AcDbSymbolTableRecord")
      '(100 . "AcDbLayerTableRecord") (cons 2 name) '(70 . 0)
      (cons 62 col) '(6 . "Continuous") (cons 370 lw))))
  (if (member key '("CENTER" "HIDDEN" "ERECT"))
    (progn
      (setq lt (rf:linetype key) en (tblobjname "LAYER" name) ed (entget en))
      (entmod (subst (cons 6 lt) (assoc 6 ed) ed))))
  name)

(defun rf:p (p off) (list (+ (car p) (car off)) (+ (cadr p) (cadr off)) 0.0))
(defun rf:unicode (txt / i out code j digit)
  (setq i 1 out "")
  (while (<= i (strlen txt))
    (if (= (substr txt i 3) "\\U+")
      (progn
        (setq code 0 j 0)
        (repeat 4
          (setq digit (ascii (strcase (substr txt (+ i 3 j) 1))))
          (setq digit (if (<= digit 57) (- digit 48) (- digit 55)))
          (setq code (+ (* code 16) digit) j (1+ j)))
        (setq out (strcat out (chr code)) i (+ i 7)))
      (setq out (strcat out (substr txt i 1)) i (1+ i))))
  out)
(defun rf:entity (o off / kind lay p1 p2 loc ang data pts dstyle fac pt txth)
  (setq kind (car o) lay (rf:layer (cadr o)))
  (cond
    ((= kind "LINE")
     (entmake (list '(0 . "LINE") '(100 . "AcDbEntity") (cons 8 lay)
       '(100 . "AcDbLine") (cons 10 (rf:p (nth 2 o) off)) (cons 11 (rf:p (nth 3 o) off)))))
    ((= kind "CIRCLE")
     (entmake (list '(0 . "CIRCLE") '(100 . "AcDbEntity") (cons 8 lay)
       '(100 . "AcDbCircle") (cons 10 (rf:p (nth 2 o) off)) (cons 40 (nth 3 o)))))
    ((= kind "ARC")
     (entmake (list '(0 . "ARC") '(100 . "AcDbEntity") (cons 8 lay)
       '(100 . "AcDbCircle") (cons 10 (rf:p (nth 2 o) off)) (cons 40 (nth 3 o))
       '(100 . "AcDbArc") (cons 50 (* pi (/ (nth 4 o) 180.0)))
       (cons 51 (* pi (/ (+ (nth 4 o) (nth 5 o)) 180.0))))))
    ((= kind "POLY")
     (setq pts (nth 3 o))
     (setq data (list '(0 . "LWPOLYLINE") '(100 . "AcDbEntity") (cons 8 lay)
       '(100 . "AcDbPolyline") (cons 90 (length pts)) (cons 70 (if (nth 2 o) 1 0))))
     (foreach pt pts
       (setq p1 (rf:p pt off))
       (setq data (append data (list (cons 10 (list (car p1) (cadr p1)))))))
     (entmake data))
    ((= kind "TEXT")
     (entmake (list '(0 . "TEXT") '(100 . "AcDbEntity") (cons 8 lay)
       '(100 . "AcDbText") (cons 10 (rf:p (nth 2 o) off))
       (cons 40 (nth 3 o)) (cons 50 (* pi (/ (nth 4 o) 180.0)))
       (cons 1 (rf:unicode (nth 5 o))) '(7 . "RF-TEXT") '(100 . "AcDbText"))))
    ((= kind "DIM")
     (setq p1 (rf:p (nth 2 o) off) p2 (rf:p (nth 3 o) off) loc (rf:p (nth 4 o) off)
       ang (* pi (/ (nth 5 o) 180.0)) fac (if (> (length o) 6) (nth 6 o) 1.0))
     (setq txth (if (> (length o) 7) (nth 7 o) 110.0))
     (setq dstyle (strcat "RF-SCALED-" (rtos fac 2 8) "-" (rtos txth 2 6)))
     (if (not (tblsearch "DIMSTYLE" dstyle))
       (entmake (list '(0 . "DIMSTYLE") '(100 . "AcDbSymbolTableRecord")
         '(100 . "AcDbDimStyleTableRecord") (cons 2 dstyle) '(70 . 0)
         '(40 . 1.0) (cons 41 (* txth 0.65)) '(42 . 40.0) '(44 . 60.0)
         (cons 140 txth) (cons 144 fac) '(147 . 45.0) '(77 . 1)
         '(271 . 3) '(78 . 8) '(277 . 2) (cons 340 (tblobjname "STYLE" "RF-TEXT")))))
     (entmake (list '(0 . "DIMENSION") '(100 . "AcDbEntity") (cons 8 lay)
       '(100 . "AcDbDimension") (cons 10 loc) (cons 11 loc) '(70 . 32) '(1 . "") (cons 3 dstyle)
       '(100 . "AcDbAlignedDimension") (cons 13 p1) (cons 14 p2)
       (cons 50 ang) '(100 . "AcDbRotatedDimension"))))
    (T (rf:fail (strcat "Unknown primitive: " kind)))))

(defun rf:font-style (/ fonts dir file chosen face pitch doc styles obj item en ed result)
  (rf:require-unicode)
  (setq dir (strcat (getenv "WINDIR") "/Fonts/"))
  ;; Use the installed font's file AND localized typeface AND GB2312 charset.
  ;; SimHei is a TTF and avoids ambiguous TTC face selection. Do not copy fonts.
  (setq fonts '(("simhei.ttf" "\\U+9ED1\\U+4F53" 38)
                ("simsun.ttc" "\\U+5B8B\\U+4F53" 22)
                ("msyh.ttc" "\\U+5FAE\\U+8F6F\\U+96C5\\U+9ED1" 38)))
  (foreach item fonts
    (if (and (not chosen) (setq file (findfile (strcat dir (car item)))))
      (setq chosen file face (rf:unicode (cadr item)) pitch (caddr item))))
  (if (not chosen) (rf:fail "No supported Chinese font found in Windows Fonts. Install SimHei/SimSun/Microsoft YaHei first."))
  (setq doc (vla-get-ActiveDocument (vlax-get-acad-object)) styles (vla-get-TextStyles doc))
  (if (tblsearch "STYLE" "RF-TEXT")
    (setq obj (vla-Item styles "RF-TEXT"))
    (progn
      (setq obj (vla-Add styles "RF-TEXT"))
      (vla-put-Height obj 0.0) (vla-put-Width obj 0.8)))
  ;; Always refresh an existing RF-TEXT style: old substituted metadata persists.
  ;; ActiveX BigFontFile explicitly rejects an empty string. DXF STYLE code 4
  ;; supports an empty value and preserves existing references to this style.
  (setq en (tblobjname "STYLE" "RF-TEXT") ed (entget en))
  (if (not (entmod (if (assoc 4 ed) (subst '(4 . "") (assoc 4 ed) ed)
                    (append ed (list '(4 . ""))))))
    (rf:fail "Cannot clear RF-TEXT Big Font (STYLE DXF code 4)."))
  (vla-put-FontFile obj chosen)
  (vla-SetFont obj face :vlax-false :vlax-false 134 pitch)
  (if (/= (cdr (assoc 4 (entget en))) "")
    (rf:fail "RF-TEXT still has a Big Font; drawing cancelled."))
  (if (/= (strcase (vl-filename-base (vla-get-FontFile obj))) (strcase (vl-filename-base chosen)))
    (rf:fail "RF-TEXT FontFile read-back differs from the selected font."))
  obj)

(defun rf:styles (/ spec)
  (rf:font-style)
  (foreach spec '(("RF-DIM" 1.0) ("RF-DIM-HALF" 0.5))
    (if (not (tblsearch "DIMSTYLE" (car spec)))
      (entmake (list '(0 . "DIMSTYLE") '(100 . "AcDbSymbolTableRecord")
        '(100 . "AcDbDimStyleTableRecord") (cons 2 (car spec)) '(70 . 0)
        '(40 . 1.0) '(41 . 80.0) '(42 . 40.0) '(44 . 60.0) '(140 . 110.0)
        (cons 144 (cadr spec)) '(147 . 45.0) '(77 . 1) '(271 . 0) '(277 . 2)
        (cons 340 (tblobjname "STYLE" "RF-TEXT")))))))

(defun c:RFFONTFIX (/ *error* doc started)
  (setq doc (vla-get-ActiveDocument (vlax-get-acad-object)))
  (defun *error* (msg)
    (if started (vla-EndUndoMark doc))
    (princ (strcat "\nRFFONTFIX stopped: " msg)) (princ))
  (rf:require-unicode)
  (vla-StartUndoMark doc) (setq started T)
  (rf:font-style)
  (vla-Regen doc 1)
  (vla-EndUndoMark doc) (setq started nil)
  (princ "\nRF-TEXT font updated. Existing text content and geometry were NOT replaced.")
  (princ "\nIf question marks remain, run RFDIAG and select a broken TEXT object.")
  (princ))

(defun c:RFDIAG (/ result obj face bold italic charset pitch selected ed txt codes questions nonascii n)
  (princ "\n--- RCFLOOR 1.5 REPORT SYNC FONTFIX diagnostics (read-only) ---")
  (princ (strcat "\nLISPSYS setting: " (itoa (getvar "LISPSYS"))))
  (setq result (vl-catch-all-apply 'rf:unicode-probe '()))
  (princ "\nActive chr/ASCII round trip (expected 20013): ")
  (if (vl-catch-all-error-p result) (princ "ERROR - restart required") (princ result))
  (if (tblsearch "STYLE" "RF-TEXT")
    (progn
      (setq obj (vla-Item (vla-get-TextStyles (vla-get-ActiveDocument (vlax-get-acad-object))) "RF-TEXT"))
      (vla-GetFont obj 'face 'bold 'italic 'charset 'pitch)
      (princ (strcat "\nFontFile: " (vla-get-FontFile obj)))
      (princ "\nBig Font DXF 4 (expected empty): ")
      (prin1 (cdr (assoc 4 (entget (tblobjname "STYLE" "RF-TEXT")))))
      (princ "\nTypeface: ") (princ face)
      (princ "\nCharset (Chinese fix expects 134): ") (princ charset)))
  (setq selected (entsel "\nSelect a broken TEXT object, or Enter to finish: "))
  (if selected
    (progn
      (setq ed (entget (car selected)))
      (if (= (cdr (assoc 0 ed)) "TEXT")
        (progn
          (setq txt (cdr (assoc 1 ed)) codes (vl-string->list txt) questions 0 nonascii 0)
          (foreach n codes
            (if (= n 63) (setq questions (1+ questions)))
            (if (> n 255) (setq nonascii (1+ nonascii))))
          (princ "\nEntity style: ") (princ (cdr (assoc 7 ed)))
          (princ "\nStored text: ") (prin1 txt)
          (princ "\nStored character codes: ") (prin1 codes)
          (princ "\nLiteral question-mark count (code 63): ") (princ questions)
          (princ "\nCharacters above code 255: ") (princ nonascii)
          (if (> questions 0)
            (princ "\nStored '?' cannot be recovered by fonts. For generated labels, reload original data and redraw in a NEW drawing.")))
        (princ "\nSelected object is not TEXT. Select an RF label rather than a dimension."))))
  (princ))

(defun rf:read (path / fh line txt datum)
  (setq *rf:data* nil)
  (if (not (setq fh (open path "r"))) (rf:fail "Cannot open floor_data.dat"))
  (setq txt "")
  (while (setq line (read-line fh)) (setq txt (strcat txt line "\n")))
  (close fh)
  (setq datum (read txt))
  (if (or (not (listp datum)) (/= (car datum) "RCFLOOR-1")) (rf:fail "Invalid RCFLOOR data version"))
  (setq *rf:data* (cdr datum))
  (princ "\nRCFLOOR data loaded.")
  (princ))

(defun c:RFLOAD (/ file)
  (setq file (getfiled "Select generated/floor_data.dat" "" "dat" 0))
  (if file (rf:read file)) (princ))

(defun rf:planwidth (/ xmax o pt)
  (setq xmax 0.0)
  (foreach o (cdr (assoc "PLAN" *rf:data*))
    (cond
      ((= (car o) "POLY")
       (foreach pt (nth 3 o) (setq xmax (max xmax (car pt)))))
      ((= (car o) "LINE") (setq xmax (max xmax (car (nth 2 o)) (car (nth 3 o)))))))
  xmax)

(defun rf:point-ok (p) (and (listp p) (>= (length p) 2) (numberp (car p)) (numberp (cadr p))))
(defun rf:preflight (groups / group entry o kind pt)
  (foreach group groups
    (setq entry (assoc group *rf:data*))
    (if (not entry) (rf:fail (strcat "Missing group: " group)))
    (foreach o (cdr entry)
      (setq kind (car o))
      (if (not (member kind '("LINE" "CIRCLE" "ARC" "POLY" "TEXT" "DIM"))) (rf:fail "Invalid primitive kind"))
      (if (not (member (cadr o) '("CONC" "REBAR" "STIRRUP" "DIM" "TEXT" "AXIS" "ENV" "CENTER" "HIDDEN" "ERECT"))) (rf:fail "Invalid layer"))
      (cond
        ((= kind "POLY") (if (< (length (nth 3 o)) 2) (rf:fail "Invalid polyline"))
          (foreach pt (nth 3 o) (if (not (rf:point-ok pt)) (rf:fail "Invalid polyline point"))))
        (T (if (not (rf:point-ok (nth 2 o))) (rf:fail "Invalid point"))))
      (if (member kind '("LINE" "DIM")) (if (not (rf:point-ok (nth 3 o))) (rf:fail "Invalid end point")))
      (if (= kind "DIM") (if (or (not (rf:point-ok (nth 4 o))) (not (numberp (nth 5 o)))) (rf:fail "Invalid dimension")))
      (if (member kind '("TEXT" "CIRCLE" "ARC")) (if (or (not (numberp (nth 3 o))) (<= (nth 3 o) 0)) (rf:fail "Invalid height/radius")))
      (if (= kind "ARC") (if (or (not (numberp (nth 4 o))) (not (numberp (nth 5 o))) (<= (nth 5 o) 0) (>= (nth 5 o) 360)) (rf:fail "Invalid arc")))
      (if (and (= kind "DIM") (> (length o) 6)) (if (or (not (numberp (nth 6 o))) (<= (nth 6 o) 0)) (rf:fail "Invalid dimension scale")))
      (if (and (= kind "DIM") (> (length o) 7)) (if (or (not (numberp (nth 7 o))) (<= (nth 7 o) 0)) (rf:fail "Invalid dimension height")))
      (if (= kind "TEXT") (if (or (not (numberp (nth 4 o))) (/= (type (nth 5 o)) 'STR)) (rf:fail "Invalid text"))))))

(defun rf:finish-draw (doc saved owned / pair result issues)
  ;; Restore each variable even when a previous restoration failed. Never end
  ;; a caller-owned undo group. Used by both normal and error exit paths.
  (foreach pair saved
    (setq result (vl-catch-all-apply 'setvar (list (car pair) (cdr pair))))
    (if (vl-catch-all-error-p result)
      (setq issues (cons (strcat (car pair) ": " (vl-catch-all-error-message result)) issues))))
  (if owned
    (progn
      (setq result (vl-catch-all-apply 'vla-EndUndoMark (list doc)))
      (if (vl-catch-all-error-p result)
        (setq issues (cons (vl-catch-all-error-message result) issues)))))
  issues)

(defun rf:draw (groups origin / *error* oldEcho oldLayer oldOsm oldUnits entry off count result group undoStarted item doc saved cleanupIssues)
  (setq oldEcho (getvar "CMDECHO") oldLayer (getvar "CLAYER")
        oldOsm (getvar "OSMODE") oldUnits (getvar "INSUNITS"))
  (setq doc (vla-get-ActiveDocument (vlax-get-acad-object))
    saved (list (cons "CMDECHO" oldEcho) (cons "CLAYER" oldLayer)
                (cons "OSMODE" oldOsm) (cons "INSUNITS" oldUnits)))
  (defun *error* (msg)
    (setq cleanupIssues (rf:finish-draw doc saved undoStarted) undoStarted nil)
    (princ (strcat "\nRCFLOOR stopped: " msg
      (if (and count (> count 0)) ". Use U to undo this drawing attempt." ". No completed entities were recorded.")))
    (if cleanupIssues (progn (princ "\nCleanup incomplete: ") (prin1 cleanupIssues))) (princ))
  (if (not *rf:data*) (c:RFLOAD))
  (if *rf:data*
    (progn
      (rf:require-unicode)
      (if (/= (getvar "TILEMODE") 1) (rf:fail "Switch to Model tab before drawing"))
      (if (not (member oldUnits '(0 4))) (rf:fail "Use a new millimetre drawing (INSUNITS=4)"))
      ;; Extra r5 sheets are optional in older data files.
      (setq groups (vl-remove-if '(lambda (g) (and (member g '("SLAB" "DIMENSIONS" "COEFF")) (not (assoc g *rf:data*)))) groups))
      (if (not groups) (rf:fail "This sheet is not available in legacy data; regenerate data with the new package."))
      (rf:preflight groups)
      (if (= 0 (logand 8 (getvar "UNDOCTL")))
        (progn (vla-StartUndoMark doc) (setq undoStarted T)))
      (setvar "CMDECHO" 0) (setvar "OSMODE" 0) (setvar "INSUNITS" 4)
      (rf:styles) (setq count 0)
      (foreach group groups
        (setq entry (assoc group *rf:data*))
        (if (not entry) (rf:fail (strcat "Missing group: " group)))
        (setq off (if (= (length groups) 1) origin
          (mapcar '+ origin (cond
            ((assoc group (cdr (assoc "OFFSETS" *rf:data*))) (cdr (assoc group (cdr (assoc "OFFSETS" *rf:data*)))))
            ((= group "PLAN") '(0.0 0.0))
            ((= group "BEAMS") '(0.0 -10000.0)) ((= group "DETAIL") '(0.0 -22000.0))
            ((= group "ENVELOPE") (list (+ (rf:planwidth) 8000.0) 13000.0))
            (T (list (+ (rf:planwidth) 8000.0) -3000.0))))))
        (foreach item (cdr entry)
          ;; Optional adapter-owned cancellation; ordinary RFALL calls are unchanged.
          (if (and (boundp '*rf:cancel-file*) *rf:cancel-file* (findfile *rf:cancel-file*))
            (rf:fail "Drawing cancelled by its owning adapter"))
          (setq result (rf:entity item off))
          (if (not result) (rf:fail (strcat "Entity creation failed in " group)))
          (setq count (1+ count))))
      ;; REGEN via command-s after UNDO End used to open a trailing empty group.
      ;; Keep regeneration and variable restoration inside our owned mark.
      (vla-Regen doc 1)
      (setq cleanupIssues (rf:finish-draw doc saved undoStarted) undoStarted nil)
      (if cleanupIssues
        (progn (princ "\nDrawing created, but cleanup incomplete: ") (prin1 cleanupIssues))
        (princ (strcat "\nCreated " (itoa count) " entities. WCS mm; review before issuing.")))))
  (princ))

(defun rf:interactive (groups / p)
  (setq p (getpoint "\nInsertion point <WCS origin>: "))
  (rf:draw groups (if p (trans p 1 0) '(0.0 0.0 0.0))) (princ))
(defun c:RFPLAN () (rf:interactive '("PLAN")))
(defun c:RFBEAMS () (rf:interactive '("BEAMS")))
(defun c:RFDETAIL () (rf:interactive '("DETAIL" "DIMENSIONS")))
(defun c:RFENV () (rf:interactive '("ENVELOPE")))
(defun c:RFTABLE () (rf:interactive '("TABLE")))
(defun c:RFSLAB () (rf:interactive '("SLAB")))
(defun c:RFDIMS () (rf:interactive '("DIMENSIONS")))
(defun c:RFCOEFF () (rf:interactive '("COEFF")))
(defun c:RFALL () (rf:interactive '("PLAN" "BEAMS" "DETAIL" "ENVELOPE" "TABLE" "SLAB" "DIMENSIONS" "COEFF")))
(princ "\nRCFLOOR 1.5 Report Sync loaded. Existing drawing: RFFONTFIX. Diagnose: RFDIAG. New drawing: RFLOAD then RFALL.")
(princ)
