;;; Run only in a disposable empty test drawing. No user geometry is erased.
(defun rfv:assert (ok msg) (if (not ok) (progn (princ msg) (exit))))
(defun rfv:count (/ s) (if (setq s (ssget "_X")) (sslength s) 0))
(defun rfv:run (data logfile / *error* f initial en ed big n saved style)
  (defun *error* (msg)
    (if f (progn (write-line (strcat "FAILED: " msg) f) (close f) (setq f nil)))
    (princ))
  (setq f (open logfile "w"))
  (rfv:assert (= (rfv:count) 0) "Use an empty new drawing")
  (rf:require-unicode)
  (setq saved (mapcar 'getvar '("CMDECHO" "CLAYER" "OSMODE" "INSUNITS")))
  (entmake '((0 . "CIRCLE") (10 -500.0 -500.0 0.0) (40 . 10.0)))
  (setq initial (entlast))
  (rf:read data)
  (rf:draw '("PLAN" "BEAMS" "DETAIL" "ENVELOPE" "TABLE" "SLAB" "DIMENSIONS" "COEFF") '(0.0 0.0 0.0))
  (setq n (1- (rfv:count)))
  (rfv:assert (> n 500) "No complete first drawing")
  (rfv:assert (equal saved (mapcar 'getvar '("CMDECHO" "CLAYER" "OSMODE" "INSUNITS"))) "Variables were not restored")
  (setq en (tblobjname "STYLE" "RF-TEXT") ed (entget en))
  (rfv:assert (= (cdr (assoc 4 ed)) "") "Big Font not empty")
  (setq big (findfile "bigfont.shx"))
  (if big
    (progn
      (entmod (subst (cons 4 big) (assoc 4 ed) ed))
      (rf:font-style)
      (rfv:assert (= (cdr (assoc 4 (entget en))) "") "Existing Big Font was not cleared")
      (write-line "Existing Big Font clearing: PASS" f))
    (write-line "Existing Big Font clearing: SKIPPED (no test SHX found)" f))
  (c:RFFONTFIX)
  (rfv:assert (= (rfv:count) (1+ n)) "Font fix changed geometry count")
  (rf:draw '("PLAN" "BEAMS" "DETAIL" "ENVELOPE" "TABLE" "SLAB" "DIMENSIONS" "COEFF") '(500000.0 0.0 0.0))
  (rfv:assert (= (rfv:count) (1+ (* n 2))) "Repeat insertion incomplete")
  (rfv:assert (entget initial) "Existing sentinel was removed")
  (rfv:assert (equal saved (mapcar 'getvar '("CMDECHO" "CLAYER" "OSMODE" "INSUNITS"))) "Variables were not restored")
  (write-line (strcat "PASS: two insertions; " (itoa n) " entities each; font fix; original entity preserved") f)
  (close f) (setq f nil) (princ))
